# Team01_StakeholderNeeds

## Cat1: Mission Capability (Container)

### N1: Runway Takeoff (Functional)
The customer needs the aircraft to take off from the runway unassisted.

### N2: Lap Count (Functional)
The customer needs the aircraft to complete three full laps of the marked course.

### N3: Cruising Altitude (Functional)
The customer needs the aircraft to reach a safe cruising altitude after takeoff

### N4: Stable Approach (Functional)
The customer needs the aircraft to perform a stabilized approach after the final lap

### N5: Landing (Functional)
The customer needs the aircraft to land on an unimproved grassy surface without damaging the aircraft

### N6: Takeoff (Functional)
The customer needs the aircraft to take off within a short length of runway

## Cat2: Safety & Environment (Functional)

### N7: Environment Safety (Functional)
The customer needs the aircraft to not create any risk of damage or injury to nearby people, wildlife, vegetation, and private property during the complete mission profile.

### N8: Battery Unobstructed (Functional)
The customer needs the handling of the battery to create no risk of touching the aircraft’s propeller.
- Keywords: RFP: Project Objectives

## Cat3: Ground Operation & Storage (Functional)

### N9: Volume Limits (Functional)
The customer needs to be able to store the aircraft in a particular volume.
- Keywords: RFP: Project Objectives

### N10: Flight Readiness (Functional)
The customer needs to be able to go from stored to flight-ready in a short time frame.
- Keywords: RFP: Project Objectives

### N11: Payload Integration (Functional)
The customer needs to be able to integrate the battery and payload in a short time frame at the field.

### N12: Battery Accessibility (Functional)
The customer needs to be able to access the battery without any tooling.

### N26: Repairability (Functional)
The customer needs the aircraft’s structure to be easily built for potential part replacements post-flight tests.

## Cat4: Payload & Battery (Functional)

### N13: Payload Requirement (Functional)
The customer needs the aircraft to be able to carry at least 1 payload during the complete mission profile.

### N14: Undamaged Components (Functional)
The customer needs the payload and battery to remain undamaged during the complete mission profile.

### N15: Unmodified Components (Functional)
The customer needs the payload and battery to be usable without any modifications.

## Cat5: Flight Test (Functional)

### N16: Payload (Functional)
The customer needs the aircraft to be stable independent of carrying a payload or not.

### N17: Pilotable (Functional)
The customer needs the aircraft to controllable and flyable by a pilot who is not part of the design team.

### N18: Telemetry (Functional)
The customer needs to be able to record and download flight telemetry gathered during flights pertaining to performance and dynamic data.

### N23: Durability (Functional)
The customer needs the aircraft to fly multiple times without the need of making edits or repairs to the structure.

### N24: Visibility (Functional)
The customer needs the aircraft to be visible throughout the complete mission profile

## Cat6: Program Constraints (Functional)

### N19: Budget (Functional)
The customer needs the aircraft to be designed and built within the available budget.

### N20: Schedule (Functional)
The customer needs the aircraft to be ready for flights within the semester schedule set forward.

### N21: Rationalization (Functional)
The customer needs any deviation in the build to be rationalized before use.

### N22: Performance Limits (Functional)
The customer needs the aircraft to meet physical and performance limits.

### N25: Design Margin (Functional)
The customer needs design to accommodate margin in the design MTOW for potential mass growth during detailed design.
