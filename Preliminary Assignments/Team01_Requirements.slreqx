# Team01_Requirements

## Cat1: Mission Capability (Functional)

### R1: Takeoff Distance (Functional)
Aircraft shall be fully airborne within 25 meters of the start line under its own power.
- Rationale: From the RFP

### R2: Post Climb Altitude (Functional)
Aircraft shall climb to 30 meters of altitude after taking off.
- Rationale: From the RFP

### R3: Lap (Functional)
Aircraft shall complete 3 full laps of the course portrayed in the RFP.
- Rationale: From the RFP

### R4: Stability (Functional)
Aircraft shall be stable when crossing the runway center-mark on lap 3.
- Rationale: From the RFP

### R5: Safe Landing (Functional)
Aircraft shall land on a dirt surface with grass up to 10 centimeters without incurring significant damage that prevents a reflight.
- Rationale: From the RFP

## Cat2: Safety & Environment (Functional)

### R6: Prevent Injury and Damage (Functional)
Aircraft shall complete the mission profile without damage to humans, vegetation, wildlife, and private property.
- Rationale: From the RFP

### R7: Battery Connection (Functional)
Aircraft shall be designed such that the battery can be connected without removing any aircraft components.
- Rationale: From the RFP

### R8: Propeller Clearance (Functional)
Aircraft shall be designed such that the battery can be connected without any appendage entering the propeller volume.
- Rationale: From the RFP

## Cat3: Ground Operations and Storage (Functional)

### R9: Storage Volume (Functional)
Aircraft shall fit within a volume of 75x75x150 cm when stored.
- Rationale: From the RFP

### R10: Wingspan (Functional)
Aircraft wingspan shall not exceed 150 cm.
- Rationale: From the RFP

### R11: Configuration Change (Functional)
Aircraft shall be able to go from storage to flight-ready in less than 5 minutes, excluding battery & payload integration.
- Rationale: From the RFP

### R12: Battery & Payload Install Time (Functional)
Aircraft shall be designed such that the payload and battery install time is no longer than 2 minutes.
- Rationale: From the RFP

### R13: Battery Access (Functional)
Aircraft shall be designed such that the removal of any panel covering the battery can be done without any tooling.
- Rationale: From the RFP

### R29: Repairability (Functional)
Aircraft shall be designed such that dis-assembling and replacing components can be performed within a 1-hour timeframe.
- Rationale: Team-added, ensures any flight-testing failures can be easily fixed without preventing a re-flight.

## Cat4: Payload Capacity (Functional)

### R14: Payload Capacity (Functional)
Aircraft shall be designed such that a minimum of 1 payload with cubic dimension of 50.8 mm (+/- 1mm) per side and mass of 520g (+/- 10g) can be carried on board throughout the mission.
- Rationale: From the RFP

### R15: Payload & Battery Mounting (Functional)
Aircraft shall retain the battery and payload securely throughout the complete mission profile.
- Rationale: From the RFP

### R16: Battery/Payload Modifications (Functional)
Aircraft’s payload and battery mounting schemes shall not require any modifications.
- Rationale: From the RFP

## Cat5: Flight Test (Functional)

### R17: Aircraft-Payload Stability (Functional)
Aircraft shall remain stable when carrying the payload during the complete mission profile.
- Rationale: From the RFP

### R18: Aircraft-No Payload Stability (Functional)
Aircraft shall remain stable when flown without payload during the complete mission profile.
- Rationale: From the RFP

### R19: Flyability (Functional)
Aircraft shall be flyable by a pilot that is not part of the team
- Rationale: From the RFP

### R20: Flight Data (Functional)
Aircraft’s avionics system shall record and download GPS altitude, climb rate, airspeed, distance flown, groundspeed, barometric altitude, load factor, turn rate, and roll rate during the complete mission profile.
- Rationale: From the RFP

### R21: Propulsion Power (Functional)
Aircraft’s propulsion system shall not draw more than 1000W of electrical power at any point during the complete mission profile.
- Rationale: From the RFP

### R26: Multiple Flights (Functional)
The aircraft shall complete 3 consecutive takeoff and landings without requiring structural repairs
- Rationale: Team-added, timeline is limited and flight tests will be performed prior to the final evaluation. Proves design robustness to multiple cycles of flight.

### R27: Tracking (Functional)
Aircraft’s exterior shall provide contrast with the flight environment for the pilot to easily track during flight at a max distance of 200 m.
- Rationale: Team-added, ensures flight failure will not occur due to momentary lack of pilot feedback control due to lack of aircraft visibility.

## Cat6: Program Constraints (Functional)

### R22: Maximum Take Off Weight (Functional)
Aircraft’s MTOW shall not exceed 6 kg mass
- Rationale: From the RFP

### R23: Budget (Functional)
The total cost of the aircraft assembly shall be no more than $400.
- Rationale: From the RFP

### R24: Schedule (Functional)
Aircraft shall be ready for flight by Week 12 of the semester.
- Rationale: From the RFP

### R25: As-Built Justifications (Functional)
Any externally sourced component shall be rationalized and submitted to the instructional team.
- Rationale: From the RFP

### R28: Weight Margin (Functional)
Aircraft’s as-designed mass shall not exceed 90% of the MTOW of 6kg.
- Rationale: Team-added, ensures any as-built mass deviations remain under the MTOW requirement.
